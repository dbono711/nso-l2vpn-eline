module l2vpn-eline {
  yang-version 1.1;
  namespace "http://dbono711/l2vpn-eline";
  prefix l2vpn-eline;

  import ietf-inet-types { prefix inet; }
  import ietf-routing-types { prefix rt-types; }
  import tailf-common { prefix tailf; }
  import tailf-ncs { prefix ncs; }

  organization
    "Darren Bono";

  contact
    "darren.bono@att.net";

  description
    "NSO service package for basic MPLS Layer 2 VPN (L2VPN) ELINE services";

  revision 2026-06-13 {
    description "Remove default MTU";
  }

  revision 2026-04-13 {
    description "Initial revision";
  }

  grouping interface {
    leaf cir {
      tailf:info "Committed Information Rate (Mbps) for interface policy";
      type uint32;
      default 1;
    }

    leaf mtu {
      tailf:info "Maximum Transmission Unit (MTU)";
      type uint32 {
        range 1500..9000;
      }
    }

    leaf port-mode {
      tailf:info "Apply service on port level";
      type boolean;
      mandatory true;
    }

    leaf efp-id {
      tailf:display-when "false()";
      tailf:info "Ethernet Flow Point ID";
      type uint16;
    }

    leaf-list vlan-id {
      tailf:info "Service encapsulation VLAN ID";
      when "../port-mode = 'false'";
      min-elements 1;
      type uint16 {
        range "1 .. 4094";
      }
    }
  }

  augment /ncs:services {
    list l2vpn-eline {
      tailf:info "MPLS Layer 2 Virtual Private Network (L2VPN) ELINE Services";
      description "mpls l2vpn elinex service package";
      key "customer-name service-id";

      uses ncs:service-data;
      ncs:servicepoint l2vpn-eline-servicepoint;

      leaf customer-name {
        tailf:info "Customer name";
        type leafref {
          path "/ncs:customers/ncs:customer/ncs:id";
        }
      }

      leaf service-id {
        tailf:info "Service identifier";
        tailf:cli-allow-range;
        type string;
      }

      leaf vpn-id {
        tailf:info "VPN identifier - used for Xconnect VC ID";
        type uint16;
      }

      container provider-edge {
        tailf:info "Provider Edge (PE) configuration";

        list device {
          tailf:info "Provider Edge device";
          max-elements 2;
          key name;

          leaf name {
            type leafref {
              path "/ncs:devices/ncs:device/ncs:name";
            }
            must "contains(/ncs:devices/ncs:device[ncs:name=current()/../name]/ncs:device-type/ncs:cli/ncs:ned-id, 'cisco-ios-cli')" {
              error-message "Provider Edge devices must be Cisco IOS";
            }
          }

          list interface {
            tailf:info "PE interface";
            max-elements 1;
            key name;

            leaf name {
              tailf:cli-completion-actionpoint l2vpn-interface-name {
                tailf:cli-completion-id "provideredge-";
              }
              type string;
            }

            uses interface;
          }
        }
      }
    }
  }
}
